--BSD 3-Clause License
--
--Copyright (c) 2018, jadeblaquiere
--All rights reserved.
--
--Redistribution and use in source and binary forms, with or without
--modification, are permitted provided that the following conditions are met:
--
--* Redistributions of source code must retain the above copyright notice, this
--  list of conditions and the following disclaimer.
--
--* Redistributions in binary form must reproduce the above copyright notice,
--  this list of conditions and the following disclaimer in the documentation
--  and/or other materials provided with the distribution.
--
--* Neither the name of the copyright holder nor the names of its
--  contributors may be used to endorse or promote products derived from
--  this software without specific prior written permission.
--
--THIS SOFTWARE IS PROVIDED BY THE COPYRIGHT HOLDERS AND CONTRIBUTORS "AS IS"
--AND ANY EXPRESS OR IMPLIED WARRANTIES, INCLUDING, BUT NOT LIMITED TO, THE
--IMPLIED WARRANTIES OF MERCHANTABILITY AND FITNESS FOR A PARTICULAR PURPOSE ARE
--DISCLAIMED. IN NO EVENT SHALL THE COPYRIGHT HOLDER OR CONTRIBUTORS BE LIABLE
--FOR ANY DIRECT, INDIRECT, INCIDENTAL, SPECIAL, EXEMPLARY, OR CONSEQUENTIAL
--DAMAGES (INCLUDING, BUT NOT LIMITED TO, PROCUREMENT OF SUBSTITUTE GOODS OR
--SERVICES; LOSS OF USE, DATA, OR PROFITS; OR BUSINESS INTERRUPTION) HOWEVER
--CAUSED AND ON ANY THEORY OF LIABILITY, WHETHER IN CONTRACT, STRICT LIABILITY,
--OR TORT (INCLUDING NEGLIGENCE OR OTHERWISE) ARISING IN ANY WAY OUT OF THE USE
--OF THIS SOFTWARE, EVEN IF ADVISED OF THE POSSIBILITY OF SUCH DAMAGE.

ForwardSecurePKE DEFINITIONS EXPLICIT TAGS ::=

BEGIN

CHKPrivateKey ::= SEQUENCE {
    pubkey  CHKPubKey,
    secrets CHKTreeNodeSecrets
}

CHKTreeNodeSecrets ::= SEQUENCE OF CHKNodeSecrets

CHKNodeSecrets ::= SEQUENCE {
    id      CHKNodeID,
    r       SEQUENCE OF OCTET STRING OPTIONAL,
    s       OCTET STRING
}

CHKNodeID ::= SEQUENCE {
    depth   INTEGER,
    ordinal INTEGER
}

CHKPublicKey ::= SEQUENCE {
    params  PairingParams,
    pPt     CurvePoint,
    qPt     CurvePoint,
    depth   INTEGER,
    order   INTEGER,
    h       IcartHash
}

CHKPubKey ::= SEQUENCE {
    params  PairingParams,
    pPt     CurvePoint,
    qPt     CurvePoint,
    depth   INTEGER,
    order   INTEGER,
    h       IcartHash
}

PairingParams ::= SEQUENCE {
    q       OCTET STRING,
    r       OCTET STRING,
    h       OCTET STRING,
    exp2    INTEGER,
    exp1    INTEGER,
    sign1   INTEGER,
    sign0   INTEGER
}

IcartHash ::= SEQUENCE {
    -- ECurve Parameters p,a,b,n const or from PairingParams q,1,0,r -- 
    g       CurvePoint,
    cwa     CarterWegmanHash,
    cwb     CarterWegmanHash
}

CurvePoint ::= SEQUENCE {
    x       OCTET STRING,
    y       OCTET STRING
}

CarterWegmanHash ::= SEQUENCE {
    p       OCTET STRING,
    --q       OCTET STRING, suppress q as it is same as PairingParams.q --
    a       OCTET STRING,
    b       OCTET STRING
}

CHKCiphertext ::= SEQUENCE {
    u       SEQUENCE OF OCTET STRING,
    v       CurvePoint
}

END
